(defun c:PSP ( / f ss i e o nm cnt a)
  (vl-load-com)
  (setq f (open (getenv "DMPOUT") "w"))
  (write-line (strcat "doc=" (getvar "DWGNAME")) f)
  (setq ss (ssget "_X") i 0 cnt nil)
  (repeat (sslength ss)
    (setq e (ssname ss i) i (1+ i))
    (setq o (vlax-ename->vla-object e))
    (setq nm (strcat (cdr (assoc 0 (entget e))) " / " (vl-catch-all-apply 'vla-get-ObjectName (list o))))
    (if (setq a (assoc nm cnt)) (setq cnt (subst (cons nm (1+ (cdr a))) a cnt)) (setq cnt (cons (cons nm 1) cnt))))
  (foreach p cnt (write-line (strcat (car p) " = " (itoa (cdr p))) f))
  (close f)
  (princ))
