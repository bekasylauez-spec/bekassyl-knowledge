(defun c:VPD ( / f ss i e)
  (setq f (open (getenv "DMPOUT") "w"))
  (setq ss (ssget "_X" '((0 . "VIEWPORT"))) i 0)
  (repeat (sslength ss)
    (setq e (entget (ssname ss i)) i (1+ i))
    (write-line (strcat (cdr (assoc 410 e)) " | id=" (itoa (cdr (assoc 69 e)))
                        " c=" (vl-princ-to-string (cdr (assoc 10 e)))
                        " w=" (rtos (cdr (assoc 40 e)) 2 3) " h=" (rtos (cdr (assoc 41 e)) 2 3)
                        " vc=" (vl-princ-to-string (cdr (assoc 12 e))) " tgt=" (vl-princ-to-string (cdr (assoc 17 e))) " vdir=" (vl-princ-to-string (cdr (assoc 16 e)))
                        " vh=" (rtos (cdr (assoc 45 e)) 2 3)
                        " scale=1:" (rtos (/ (cdr (assoc 45 e)) (cdr (assoc 41 e))) 2 4)
                        " twist=" (rtos (cdr (assoc 51 e)) 2 4)) f))
  (setq ss (ssget "_X" '((0 . "IMAGE,OLE2FRAME,INSERT"))) i 0)
  (if ss (repeat (sslength ss)
    (setq e (entget (ssname ss i)) i (1+ i))
    (write-line (strcat (cdr (assoc 0 e)) " " (vl-princ-to-string (cdr (assoc 2 e))) " at " (vl-princ-to-string (cdr (assoc 10 e)))) f)))
  (close f) (princ))
