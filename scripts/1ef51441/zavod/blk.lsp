(defun c:BLKD ( / f e ed typ n)
  (setq f (open (getenv "DMPOUT") "w"))
  (setq e (cdr (assoc -2 (tblsearch "BLOCK" (getenv "BLKNAME")))))
  (write-line (strcat "base " (vl-princ-to-string (cdr (assoc 10 (tblsearch "BLOCK" (getenv "BLKNAME")))))) f)
  (while e
    (setq ed (entget e) typ (cdr (assoc 0 ed)))
    (write-line (strcat typ " L=" (cdr (assoc 8 ed))
                        (cond ((member typ '("TEXT" "MTEXT" "ATTDEF")) (strcat " st=" (cdr (assoc 7 ed)) " h=" (rtos (cdr (assoc 40 ed)) 2 2) " p=" (vl-princ-to-string (cdr (assoc 10 ed))) " s=" (cdr (assoc 1 ed))))
                              ((= typ "LINE") (strcat " " (vl-princ-to-string (cdr (assoc 10 ed))) " " (vl-princ-to-string (cdr (assoc 11 ed))) " lw=" (vl-princ-to-string (cdr (assoc 370 ed)))))
                              ((= typ "LWPOLYLINE") (strcat " n=" (itoa (cdr (assoc 90 ed))) " w=" (vl-princ-to-string (cdr (assoc 43 ed))) " p0=" (vl-princ-to-string (cdr (assoc 10 ed)))))
                              ((= typ "INSERT") (strcat " " (cdr (assoc 2 ed)) " " (vl-princ-to-string (cdr (assoc 10 ed)))))
                              (T ""))) f)
    (setq e (entnext e)))
  (close f) (princ))
