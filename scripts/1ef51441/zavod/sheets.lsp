(defun sh:r (v) (rtos v 2 1))
(defun c:SHD ( / f ss i e ed n)
  (setq f (open (getenv "DMPOUT") "w"))
  (setq ss (ssget "_X" '((0 . "VIEWPORT"))) i 0)
  (repeat (sslength ss)
    (setq e (entget (ssname ss i)) i (1+ i))
    (if (/= 1 (cdr (assoc 69 e)))
      (write-line (strcat "VP\t" (cdr (assoc 410 e)) "\t" (sh:r (cadr (assoc 17 e))) " " (sh:r (caddr (assoc 17 e)))
                          "\t" (sh:r (/ (cdr (assoc 45 e)) (cdr (assoc 41 e)))) "\t" (sh:r (cdr (assoc 40 e))) " " (sh:r (cdr (assoc 41 e)))
                          "\t" (sh:r (- (cadr (assoc 10 e)) 0)) " " (sh:r (caddr (assoc 10 e)))) f)))
  (setq ss (ssget "_X" '((0 . "INSERT") (2 . "�����1"))) i 0)
  (if ss (repeat (sslength ss)
    (setq e (entget (ssname ss i)) i (1+ i))
    (write-line (strcat "ST\t" (cdr (assoc 410 e)) "\t" (sh:r (cadr (assoc 10 e))) " " (sh:r (caddr (assoc 10 e))) "\t" (rtos (cdr (assoc 41 e)) 2 3)) f)))
  (setq ss (ssget "_X" '((0 . "TEXT,MTEXT"))) i 0)
  (repeat (sslength ss)
    (setq e (entget (ssname ss i)) i (1+ i))
    (write-line (strcat "TX\t" (cdr (assoc 410 e)) "\t" (sh:r (cadr (assoc 10 e))) " " (sh:r (caddr (assoc 10 e))) "\t" (sh:r (cdr (assoc 40 e))) "\t" (cdr (assoc 5 e)) "\t" (vl-string-translate "\t\n" "  " (cdr (assoc 1 e)))) f))
  (close f) (princ))
