(defun c:INSD ( / f ss i e ed a n done)
  (setq f (open (getenv "DMPOUT") "w") done '())
  (setq ss (ssget "_X" '((0 . "INSERT"))) i 0)
  (repeat (sslength ss)
    (setq e (ssname ss i) i (1+ i) ed (entget e) n (cdr (assoc 2 ed)))
    (write-line (strcat "INS " n " lay=" (cdr (assoc 410 ed)) " at " (vl-princ-to-string (cdr (assoc 10 ed))) " sc=" (rtos (cdr (assoc 41 ed)) 2 3) " L=" (cdr (assoc 8 ed))) f)
    (if (and (= 1 (cdr (assoc 66 ed))) (not (member n done)))
      (progn (setq done (cons n done) a (entnext e))
        (while (and a (= "ATTRIB" (cdr (assoc 0 (entget a)))))
          (write-line (strcat "   ATT " (cdr (assoc 2 (entget a))) " = " (cdr (assoc 1 (entget a)))) f)
          (setq a (entnext a))))))
  (close f) (princ))
