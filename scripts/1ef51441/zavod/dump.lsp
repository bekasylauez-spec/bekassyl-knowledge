(defun dmp:w (s) (write-line s dmp:f))
(defun dmp:g (k e) (cdr (assoc k e)))
(defun dmp:inc (key lst / a)
  (if (setq a (assoc key lst))
    (subst (cons key (1+ (cdr a))) a lst)
    (cons (cons key 1) lst)))
(defun c:DMP ( / out d e n ss i ent typ lay h cnt hts sty dst lts)
  (setq out (getenv "DMPOUT"))
  (setq dmp:f (open out "w"))
  (dmp:w "== STYLE")
  (setq d (tblnext "STYLE" T))
  (while d
    (dmp:w (strcat (dmp:g 2 d) " | font=" (vl-princ-to-string (dmp:g 3 d)) " big=" (vl-princ-to-string (dmp:g 4 d))
                   " h=" (rtos (dmp:g 40 d) 2 3) " w=" (rtos (dmp:g 41 d) 2 3) " obl=" (rtos (* 180 (/ (dmp:g 50 d) pi)) 2 1)))
    (setq d (tblnext "STYLE")))
  (dmp:w "== DIMSTYLE")
  (setq d (tblnext "DIMSTYLE" T))
  (while d
    (setq e (entget (tblobjname "DIMSTYLE" (dmp:g 2 d))))
    (dmp:w (strcat (dmp:g 2 d) " | txt=" (rtos (cond ((dmp:g 140 e)) (0)) 2 2) " scale=" (rtos (cond ((dmp:g 40 e)) (1)) 2 2)
                   " asz=" (rtos (cond ((dmp:g 41 e)) (0)) 2 2) " gap=" (rtos (cond ((dmp:g 147 e)) (0)) 2 2)
                   " exo=" (rtos (cond ((dmp:g 42 e)) (0)) 2 2) " exe=" (rtos (cond ((dmp:g 44 e)) (0)) 2 2)
                   " tsz=" (rtos (cond ((dmp:g 142 e)) (0)) 2 2) " lfac=" (rtos (cond ((dmp:g 144 e)) (1)) 2 3)
                   " tad=" (vl-princ-to-string (dmp:g 77 e)) " tih=" (vl-princ-to-string (dmp:g 73 e))
                   " tmove=" (vl-princ-to-string (dmp:g 279 e))
                   " txsty=" (if (dmp:g 340 e) (dmp:g 2 (entget (dmp:g 340 e))) "-")
                   " blk=" (if (dmp:g 342 e) (dmp:g 2 (entget (dmp:g 342 e))) "-")
                   " blk1=" (if (dmp:g 343 e) (dmp:g 2 (entget (dmp:g 343 e))) "-")
                   " clrd=" (vl-princ-to-string (dmp:g 176 e)) " clre=" (vl-princ-to-string (dmp:g 177 e)) " clrt=" (vl-princ-to-string (dmp:g 178 e))))
    (setq d (tblnext "DIMSTYLE")))
  (dmp:w "== MLEADERSTYLE")
  (if (setq d (dictsearch (namedobjdict) "ACAD_MLEADERSTYLE"))
    (foreach p d (if (= (car p) 3) (dmp:w (cdr p)))))
  (dmp:w "== LAYOUTS")
  (if (setq d (dictsearch (namedobjdict) "ACAD_LAYOUT"))
    (foreach p d (if (= (car p) 3) (dmp:w (cdr p)))))
  (dmp:w "== LAYER")
  (setq d (tblnext "LAYER" T))
  (while d
    (dmp:w (strcat (dmp:g 2 d) " | c=" (itoa (dmp:g 62 d)) " lt=" (dmp:g 6 d) " lw=" (vl-princ-to-string (dmp:g 370 (entget (tblobjname "LAYER" (dmp:g 2 d)))))))
    (setq d (tblnext "LAYER")))
  (dmp:w "== ENTITIES (space|type|layer|style) count")
  (setq cnt nil hts nil)
  (setq ss (ssget "_X"))
  (setq i 0)
  (if ss
    (repeat (sslength ss)
      (setq e (entget (ssname ss i)) i (1+ i))
      (setq typ (dmp:g 0 e))
      (setq sty (cond ((member typ '("TEXT" "MTEXT" "ATTDEF")) (vl-princ-to-string (dmp:g 7 e)))
                      ((= typ "DIMENSION") (vl-princ-to-string (dmp:g 3 e)))
                      ((= typ "INSERT") (vl-princ-to-string (dmp:g 2 e)))
                      (T "")))
      (setq cnt (dmp:inc (strcat (if (= 1 (dmp:g 67 e)) (vl-princ-to-string (dmp:g 410 e)) "Model") "|" typ "|" (dmp:g 8 e) "|" sty) cnt))
      (if (member typ '("TEXT" "MTEXT"))
        (setq hts (dmp:inc (strcat (if (= 1 (dmp:g 67 e)) "PS" "MS") " " typ " " (vl-princ-to-string (dmp:g 7 e)) " h=" (rtos (dmp:g 40 e) 2 2)) hts)))))
  (foreach p (vl-sort cnt '(lambda (a b) (< (car a) (car b)))) (dmp:w (strcat (car p) " = " (itoa (cdr p)))))
  (dmp:w "== TEXT HEIGHTS")
  (foreach p (vl-sort hts '(lambda (a b) (< (car a) (car b)))) (dmp:w (strcat (car p) " = " (itoa (cdr p)))))
  (close dmp:f)
  (princ))
