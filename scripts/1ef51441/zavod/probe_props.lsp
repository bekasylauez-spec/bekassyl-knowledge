(defun pp:main ( / f ss i e o nm done)
  (vl-load-com)
  (setq ss (ssget "_X") i 0 done '())
  (repeat (sslength ss)
    (setq e (ssname ss i) i (1+ i))
    (setq nm (cdr (assoc 0 (entget e))))
    (if (and (wcmatch nm "SPDS*") (not (member nm done)))
      (progn
        (setq done (cons nm done))
        (setq o (vlax-ename->vla-object e))
        (princ (strcat "\n########## " nm " layout=" (vl-princ-to-string (cdr (assoc 410 (entget e))))))
        (vl-catch-all-apply 'vlax-dump-object (list o T))))))
(defun c:PPR ( / r)
  (vl-load-com)
  (setvar "LOGFILEMODE" 1)
  (vl-catch-all-apply 'setvar (list "LOGFILEPATH" (getenv "PPDIR")))
  (command "_.LOGFILEON")
  (setq r (vl-catch-all-apply 'pp:main nil))
  (if (vl-catch-all-error-p r) (princ (strcat "\nERR " (vl-catch-all-error-message r))))
  (princ (strcat "\nLOGFILE=" (getvar "LOGFILENAME")))
  (command "_.LOGFILEOFF")
  (setvar "LOGFILEMODE" 0)
  (command "_.QUIT" "_Y")
  (princ))
