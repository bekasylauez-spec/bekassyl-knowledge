(defun geo:r (v) (rtos v 2 4))
(defun geo:p (p) (strcat (geo:r (car p)) " " (geo:r (cadr p))))
(defun geo:in (p) (and p (>= (car p) geo:x0) (<= (car p) geo:x1) (>= (cadr p) geo:y0) (<= (cadr p) geo:y1)))
(defun c:GEO ( / f ss i e typ p ok h vs)
  (setq geo:x0 (atof (getenv "GX0")) geo:x1 (atof (getenv "GX1")) geo:y0 (atof (getenv "GY0")) geo:y1 (atof (getenv "GY1")))
  (setq f (open (getenv "DMPOUT") "w"))
  (setq ss (ssget "_X" '((410 . "Model"))) i 0)
  (repeat (sslength ss)
    (setq e (entget (ssname ss i)) i (1+ i))
    (setq typ (cdr (assoc 0 e)) h (cdr (assoc 5 e)))
    (cond
      ((= typ "LINE")
       (if (or (geo:in (cdr (assoc 10 e))) (geo:in (cdr (assoc 11 e))))
         (write-line (strcat "L\t" h "\t" (geo:p (cdr (assoc 10 e))) " " (geo:p (cdr (assoc 11 e)))) f)))
      ((= typ "CIRCLE")
       (if (geo:in (cdr (assoc 10 e)))
         (write-line (strcat "C\t" h "\t" (geo:p (cdr (assoc 10 e))) " " (geo:r (cdr (assoc 40 e)))) f)))
      ((= typ "ARC")
       (if (geo:in (cdr (assoc 10 e)))
         (write-line (strcat "A\t" h "\t" (geo:p (cdr (assoc 10 e))) " " (geo:r (cdr (assoc 40 e))) " " (geo:r (cdr (assoc 50 e))) " " (geo:r (cdr (assoc 51 e)))) f)))
      ((= typ "TEXT")
       (if (geo:in (cdr (assoc 10 e)))
         (write-line (strcat "T\t" h "\t" (geo:p (cdr (assoc 10 e))) " " (geo:p (cdr (assoc 11 e))) " " (geo:r (cdr (assoc 40 e)))
                             " " (geo:r (cdr (assoc 50 e))) " " (geo:r (cdr (assoc 41 e))) " " (geo:r (cdr (assoc 51 e)))
                             " " (itoa (cdr (assoc 72 e))) " " (itoa (cdr (assoc 73 e))) "\t" (cdr (assoc 7 e)) "\t" (cdr (assoc 1 e))) f)))
      ((= typ "MTEXT")
       (if (geo:in (cdr (assoc 10 e)))
         (write-line (strcat "M\t" h "\t" (geo:p (cdr (assoc 10 e))) " " (geo:r (cdr (assoc 40 e))) "\t" (cdr (assoc 7 e)) "\t" (apply (quote strcat) (mapcar (quote cdr) (vl-remove-if-not (quote (lambda (p) (= (car p) 3))) e))) (cdr (assoc 1 e))) f)))
      ((member typ '("LWPOLYLINE" "POLYLINE" "SPLINE" "HATCH" "SOLID" "WIPEOUT" "IMAGE" "INSERT" "OLE2FRAME"))
       (setq p (cdr (assoc 10 e)))
       (if (and (= typ "POLYLINE")) (setq p (cdr (assoc 10 (entget (entnext (ssname ss (1- i))))))))
       (if (and (= typ "HATCH")) (setq p (cdr (assoc 10 (member (assoc 92 e) e)))))
       (if (geo:in p)
         (progn
           (setq vs "")
           (if (= typ "LWPOLYLINE")
             (foreach q e (if (= (car q) 10) (setq vs (strcat vs " " (geo:p (cdr q)))))))
           (if (= typ "SOLID")
             (foreach k '(10 11 12 13) (setq vs (strcat vs " " (geo:p (cdr (assoc k e)))))))
           (if (= typ "WIPEOUT")
             (foreach q e (if (= (car q) 14) (setq vs (strcat vs " " (geo:p (cdr q)))))))
           (write-line (strcat (substr typ 1 2) "\t" h "\t" (geo:p p) "\t" (itoa (cond ((cdr (assoc 70 e))) (0))) "\t" vs) f))))))
  (close f) (princ))
