(defun c:DMP (/ ss i e f typ)
  (setq f (open (strcat "C:/Users/beka/AppData/Local/Temp/claude/D---------------/72af3b3f-2397-48af-af38-773774531e1c/scratchpad/ar/" (getvar "DWGNAME") "_dmp.txt") "w"))
  (setq ss (ssget "_X" '((410 . "Model") (-4 . "<OR") (0 . "INSERT") (0 . "TEXT") (0 . "MTEXT") (-4 . "OR>"))))
  (setq i 0)
  (if ss (repeat (sslength ss)
    (setq e (entget (ssname ss i)) i (1+ i) typ (cdr (assoc 0 e)))
    (princ typ f) (princ "\t" f)
    (if (= typ "INSERT") (progn (princ (cdr (assoc 2 e)) f) (princ "\t" f) (princ (cdr (assoc 41 e)) f))
        (progn (princ (cdr (assoc 1 e)) f) (princ "\t" f) (princ (cdr (assoc 40 e)) f)))
    (princ "\t" f) (princ (cdr (assoc 10 e)) f) (princ "\n" f)))
  (close f) (princ))
