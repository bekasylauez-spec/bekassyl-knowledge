(defun wr (f l) (princ l f) (princ "\n" f))
(defun dumpwin (fn p1 p2 / ss i e f typ v)
  (setq f (open fn "w"))
  (setq ss (ssget "_C" p1 p2))
  (setq i 0)
  (if ss (repeat (sslength ss)
    (setq e (entget (ssname ss i)) i (1+ i) typ (cdr (assoc 0 e)))
    (cond
      ((= typ "LINE") (wr f (list "L" (cdr (assoc 8 e)) (cdr (assoc 10 e)) (cdr (assoc 11 e)))))
      ((= typ "LWPOLYLINE") (princ (list "P" (cdr (assoc 8 e)) (cdr (assoc 70 e))) f)
         (foreach g e (if (member (car g) '(10 42)) (princ (list (car g) (cdr g)) f))) (princ "\n" f))
      ((= typ "ARC") (wr f (list "A" (cdr (assoc 8 e)) (cdr (assoc 10 e)) (cdr (assoc 40 e)) (cdr (assoc 50 e)) (cdr (assoc 51 e)))))
      ((= typ "CIRCLE") (wr f (list "C" (cdr (assoc 8 e)) (cdr (assoc 10 e)) (cdr (assoc 40 e)))))
      ((= typ "INSERT") (wr f (list "I" (cdr (assoc 8 e)) (cdr (assoc 2 e)) (cdr (assoc 10 e)) (cdr (assoc 41 e)) (cdr (assoc 50 e)))))
      ((member typ '("TEXT" "MTEXT")) (wr f (list "T" (cdr (assoc 1 e)) (cdr (assoc 10 e)))))
      (T (wr f (list typ (cdr (assoc 8 e))))))))
  (close f) (princ))
