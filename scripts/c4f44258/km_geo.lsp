; Full-precision geometry dump of the model space (blocks exploded first; the drawing is not saved).
(defun _r (v) (rtos v 2 3))
(defun _pt (p) (strcat (_r (car p)) " " (_r (cadr p))))
(defun _x1 ( / ss i e n)
  (setq n 0)
  (if (setq ss (ssget "X" '((0 . "INSERT,DIMENSION,MLINE,REGION") (410 . "Model"))))
    (progn (setq i 0)
      (repeat (sslength ss) (setq e (ssname ss i)) (if (entget e) (progn (command "_.EXPLODE" e "") (setq n (1+ n)))) (setq i (1+ i)))))
  n)
(defun c:KMGEO ( / f ss i ed ty pass n str)
  (setvar "CMDECHO" 0) (setvar "QAFLAGS" 1)
  (setq pass 0 n 1)
  (while (and (< pass 6) (> n 0)) (setq pass (1+ pass) n (_x1)))
  (setvar "QAFLAGS" 0)
  (setq f (open "C:/Users/beka/AppData/Local/Temp/claude/D---------------/c4f44258-6943-4b10-8e73-e6f1e42efec6/scratchpad/km_geo.txt" "w"))
  (if (setq ss (ssget "X" '((410 . "Model"))))
    (progn (setq i 0)
      (repeat (sslength ss)
        (setq ed (entget (ssname ss i)) ty (cdr (assoc 0 ed)))
        (cond
          ((= ty "LINE") (write-line (strcat "L|" (cdr (assoc 8 ed)) "|" (_pt (cdr (assoc 10 ed))) "|" (_pt (cdr (assoc 11 ed)))) f))
          ((= ty "LWPOLYLINE")
            (setq str (strcat "P|" (cdr (assoc 8 ed)) "|" (itoa (cdr (assoc 70 ed)))))
            (foreach x ed (cond ((= (car x) 10) (setq str (strcat str "|" (_pt (cdr x)))))
                                ((= (car x) 42) (if (/= (cdr x) 0.0) (setq str (strcat str "~" (_r (cdr x))))))))
            (write-line str f))
          ((= ty "CIRCLE") (write-line (strcat "C|" (cdr (assoc 8 ed)) "|" (_pt (cdr (assoc 10 ed))) "|" (_r (cdr (assoc 40 ed)))) f))
          ((= ty "ARC") (write-line (strcat "A|" (cdr (assoc 8 ed)) "|" (_pt (cdr (assoc 10 ed))) "|" (_r (cdr (assoc 40 ed))) "|" (rtos (cdr (assoc 50 ed)) 2 6) "|" (rtos (cdr (assoc 51 ed)) 2 6)) f))
          ((member ty '("TEXT" "MTEXT")) (write-line (strcat "T|" (cdr (assoc 8 ed)) "|" (_pt (cdr (assoc 10 ed))) "|" (_r (cdr (assoc 40 ed))) "|" (cdr (assoc 1 ed))) f))
        )
        (setq i (1+ i)))))
  (close f) (princ))
