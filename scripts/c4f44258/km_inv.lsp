; KM inventory without exploding: layouts + viewports, and every Model entity reduced to its essentials (one line each).
(defun _p (f lst) (prin1 lst f) (princ "\n" f))
(defun _g (code ed) (cdr (assoc code ed)))
(defun c:KMINV ( / f ss i e ed ty d lay ent)
  (setvar "CMDECHO" 0)
  (setq f (open "C:/Users/beka/AppData/Local/Temp/claude/D---------------/c4f44258-6943-4b10-8e73-e6f1e42efec6/scratchpad/km_inv.txt" "w"))
  ; layouts
  (setq d (dictsearch (namedobjdict) "ACAD_LAYOUT"))
  (foreach pr d (if (= (car pr) 3) (_p f (list "LAYOUT" (cdr pr)))))
  ; layers
  (setq lay (tblnext "LAYER" T))
  (while lay (_p f (list "LAYER" (_g 2 lay) (_g 62 lay))) (setq lay (tblnext "LAYER")))
  ; viewports in paper space (which model window each sheet shows)
  (if (setq ss (ssget "X" '((0 . "VIEWPORT"))))
    (progn (setq i 0)
      (repeat (sslength ss) (setq ed (entget (ssname ss i)))
        (_p f (list "VP" (_g 410 ed) (_g 10 ed) (_g 40 ed) (_g 41 ed) (_g 12 ed) (_g 45 ed) (_g 69 ed))) (setq i (1+ i)))))
  ; model space
  (if (setq ss (ssget "X" '((410 . "Model"))))
    (progn (setq i 0)
      (repeat (sslength ss)
        (setq ed (entget (ssname ss i)) ty (_g 0 ed))
        (cond
          ((= ty "LINE") (_p f (list "L" (_g 8 ed) (_g 10 ed) (_g 11 ed))))
          ((= ty "LWPOLYLINE") (_p f (list "PL" (_g 8 ed) (_g 70 ed) (vl-remove-if-not '(lambda (x) (= (car x) 10)) ed))))
          ((= ty "CIRCLE") (_p f (list "C" (_g 8 ed) (_g 10 ed) (_g 40 ed))))
          ((= ty "ARC") (_p f (list "A" (_g 8 ed) (_g 10 ed) (_g 40 ed) (_g 50 ed) (_g 51 ed))))
          ((= ty "TEXT") (_p f (list "T" (_g 8 ed) (_g 10 ed) (_g 40 ed) (_g 50 ed) (_g 1 ed))))
          ((= ty "MTEXT") (_p f (list "MT" (_g 8 ed) (_g 10 ed) (_g 40 ed) (_g 1 ed))))
          ((= ty "DIMENSION") (_p f (list "D" (_g 8 ed) (_g 42 ed) (_g 1 ed) (_g 10 ed) (_g 13 ed) (_g 14 ed) (_g 11 ed))))
          ((= ty "INSERT") (_p f (list "I" (_g 8 ed) (_g 2 ed) (_g 10 ed) (_g 41 ed) (_g 50 ed))))
          (T (_p f (list "X" ty (_g 8 ed))))
        )
        (setq i (1+ i)))))
  (close f) (princ))
