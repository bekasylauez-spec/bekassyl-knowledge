(vl-load-com)
(setq *S* "C:/Users/Admin/AppData/Local/Temp/claude/210ab68cad67e8c1/4c62aff2-a55a-4637-9af2-523dd75c9ccb/scratchpad/")
(defun logm (s / f) (setq f (open (strcat *S* "p4_log.txt") "a")) (write-line s f) (close f))
(defun mklay (n lw) (if (not (tblsearch "LAYER" n)) (command "_.-LAYER" "_N" n "_LW" lw n "")))
(defun rc (lay a b)
  (entmake (list '(0 . "LWPOLYLINE") '(100 . "AcDbEntity") (cons 8 lay) '(100 . "AcDbPolyline") '(90 . 4) '(70 . 1)
    (cons 10 (list (car a) (cadr a))) (cons 10 (list (car b) (cadr a)))
    (cons 10 (list (car b) (cadr b))) (cons 10 (list (car a) (cadr b))))))
(defun pl (lay pts cl)
  (entmake (append (list '(0 . "LWPOLYLINE") '(100 . "AcDbEntity") (cons 8 lay) '(100 . "AcDbPolyline")
    (cons 90 (length pts)) (cons 70 (if cl 1 0)))
    (mapcar '(lambda (p) (cons 10 p)) pts))))
(defun ln (lay a b) (entmake (list '(0 . "LINE") (cons 8 lay) (cons 10 a) (cons 11 b))))
(defun tx (lay p h s rot j)
  (entmake (list '(0 . "TEXT") (cons 8 lay) (cons 7 "Isocpeur") (cons 10 p) (cons 11 p) (cons 40 h) (cons 1 s)
    (cons 50 rot) (cons 72 (if (= j "ML") 0 1)) (cons 73 2))))
(defun dn (p d / ol) (setq ol (getvar "CLAYER")) (setvar "CLAYER" "КЖ_Арматура") (command "_.DONUT" 0 d p "") (setvar "CLAYER" ol))
(defun dl (a b c f / ol) (setq ol (getvar "CLAYER")) (setvar "CLAYER" "Размеры") (setvar "DIMLFAC" f)
  (command "_.DIMLINEAR" a b c) (setvar "DIMLFAC" 1.0) (setvar "CLAYER" ol))
(defun settext (e s / d) (setq d (entget e)) (entmod (subst (cons 1 s) (assoc 1 d) d)))
(defun cpy (e dx dy) (command "_.COPY" e "" "0,0" (strcat (rtos dx 2 2) "," (rtos dy 2 2)) "") (entlast))
(defun sheetk (dx num name ttl)
  (cpy (handent "1E6700") dx 0.0)
  (cpy (handent "1E6701") dx 0.0)
  (settext (cpy (handent "1E6702") dx 0.0) name)
  (settext (cpy (handent "1E6704") dx 0.0) num)
  (if ttl (settext (cpy (handent "1E6706") dx 0.0) ttl))
  (logm (strcat "sheet " num)))
(defun plancp (lst dx xn / ss e)
  (setq ss (ssadd))
  (foreach h lst (if (setq e (handent h)) (ssadd e ss)))
  (logm (strcat "plan n=" (itoa (sslength ss))))
  (command "_.COPY" ss "" "0,0" (strcat (rtos dx 2 2) ",0") ""))
(defun plancp2 (lst dx dy / ss e)
  (setq ss (ssadd))
  (foreach h lst (if (setq e (handent h)) (ssadd e ss)))
  (logm (strcat "plan n=" (itoa (sslength ss))))
  (command "_.COPY" ss "" "0,0" (strcat (rtos dx 2 2) "," (rtos dy 2 2)) ""))
(defun bb (e / o a b r)
  (setq o (vlax-ename->vla-object e))
  (setq r (vl-catch-all-apply 'vla-getboundingbox (list o 'a 'b)))
  (if (vl-catch-all-error-p r) nil (list (vlax-safearray->list a) (vlax-safearray->list b))))
(defun dlt (a b c f txt / ol d) (setq ol (getvar "CLAYER")) (setvar "CLAYER" "Размеры") (setvar "DIMLFAC" f)
  (command "_.DIMLINEAR" a b c) (setvar "DIMLFAC" 1.0) (setvar "CLAYER" ol)
  (if txt (progn (setq d (entget (entlast))) (entmod (subst (cons 1 txt) (assoc 1 d) d)))))
(defun dn2 (p d lay / ol) (setq ol (getvar "CLAYER")) (setvar "CLAYER" lay) (command "_.DONUT" 0 d p "") (setvar "CLAYER" ol))
(defun hl (/ e ol) (setq e (entlast) ol (getvar "CLAYER")) (setvar "CLAYER" "КЖ_Штрих")
  (command "_.-HATCH" "_P" "ANSI36" "20" "0" "_S" e "" "") (setvar "CLAYER" ol))
(defun seccp (tgt / ss i e b w h done)
  (setq ss (ssget "_X" '((0 . "SPDSSECTION"))) i 0 done nil)
  (while (and ss (< i (sslength ss)) (not done))
    (setq e (ssname ss i) b (bb e))
    (if b (progn (setq w (- (car (cadr b)) (car (car b))) h (- (cadr (cadr b)) (cadr (car b))))
      (if (and (> w h) (> (car (car b)) -393823.0) (< (car (cadr b)) -351823.0))
        (progn (cpy e (- (car tgt) (/ (+ (car (car b)) (car (cadr b))) 2.0)) (- (cadr tgt) (/ (+ (cadr (car b)) (cadr (cadr b))) 2.0)))
               (setq done T) (logm "seccp ok")))))
    (setq i (1+ i)))
  (if (not done) (logm "seccp NOT FOUND")));;BODY
(defun c:P4 (/ r)
  (setvar "CMDECHO" 0) (setvar "OSMODE" 0)
  (mklay "КЖ_Фундамент" "0.30") (mklay "КЖ_Арматура" "0.40") (mklay "КЖ_ФБС" "0.30") (mklay "КЖ_Штрих" "0.05")
  (mklay "КЖ_Марки" "0.05") (mklay "КЖ_Таблица" "0.05") (mklay "КЖ_Таблица_т" "0.30") (mklay "диам20" "0.40") (mklay "диам12" "0.40") (mklay "диам8" "0.30")
  (if (tblsearch "DIMSTYLE" "СПДС") (command "_.-DIMSTYLE" "_R" "СПДС"))
  (setq r (vl-catch-all-apply 'p4_body nil))
  (if (vl-catch-all-error-p r) (logm (strcat "ERR " (vl-catch-all-error-message r))) (logm "body ok"))
  (command "_.ZOOM" "_E")
  (logm "saved")
  (princ))
