(vl-load-com)
(setq *S* "C:/Users/Admin/AppData/Local/Temp/claude/210ab68cad67e8c1/4c62aff2-a55a-4637-9af2-523dd75c9ccb/scratchpad/")
(defun bb (e / o a b r)
  (setq o (vlax-ename->vla-object e))
  (setq r (vl-catch-all-apply 'vla-getboundingbox (list o 'a 'b)))
  (if (vl-catch-all-error-p r) nil (list (vlax-safearray->list a) (vlax-safearray->list b))))
(defun inbox (b x0 y0 x1 y1) (and b (>= (car (car b)) x0) (>= (cadr (car b)) y0) (<= (car (cadr b)) x1) (<= (cadr (cadr b)) y1)))
(defun c:P1 (/ f ss i e d b h keep ex tb r c o)
  (setq f (open (strcat *S* "p1_dump.txt") "w"))
  (setq ss (ssget "_X" '((410 . "Model"))) i 0 keep (ssadd))
  (setq ex '("1A67A9" "1A67AA" "1B85A7" "1B85A8"))
  (while (< i (sslength ss))
    (setq e (ssname ss i) d (entget e) h (cdr (assoc 5 d)) b (bb e))
    (if (and b (inbox b -488400 -574800 -404200 -544900))
      (progn
        (write-line (strcat h ";" (cdr (assoc 0 d)) ";" (cdr (assoc 8 d)) ";"
          (rtos (car (car b)) 2 0) ";" (rtos (cadr (car b)) 2 0) ";" (rtos (car (cadr b)) 2 0) ";" (rtos (cadr (cadr b)) 2 0)) f)
        (if (and (not (member h ex))
                 (not (and (= (cdr (assoc 8 d)) "�_������") (< (cadr (car b)) -568700))))
          (ssadd e keep))))
    (setq i (1+ i)))
  (foreach th '("1B853C" "1B8562")
    (setq o (vlax-ename->vla-object (handent th)))
    (write-line (strcat "TABLE " th " " (itoa (vla-get-rows o)) "x" (itoa (vla-get-columns o))) f)
    (setq r 0)
    (repeat (vla-get-rows o)
      (setq c 0)
      (repeat (vla-get-columns o)
        (write-line (strcat "C;" th ";" (itoa r) ";" (itoa c) ";" (vla-gettext o r c)) f)
        (setq c (1+ c)))
      (setq r (1+ r))))
  (write-line (strcat "KEEP " (itoa (sslength keep))) f)
  (close f)
  (command "_.-WBLOCK" (strcat *S* "analog45.dwg") "" "0,0" keep "")
  (setq f (open (strcat *S* "p1_dump.txt") "a")) (write-line "WBLOCK done" f) (close f)
  (princ))
