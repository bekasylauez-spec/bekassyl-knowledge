(vl-load-com)
(setq *S* "C:/Users/Admin/AppData/Local/Temp/claude/210ab68cad67e8c1/4c62aff2-a55a-4637-9af2-523dd75c9ccb/scratchpad/")
(setq *X35* -393823.0 *Y0* -992318.0 *TBL* nil)
(setq *OX* '(-481598.0 -477098.0 -473098.0 -469298.0 -465298.0 -460798.0) *NU* '(0.0 4300.0 8950.0 12650.0 17300.0 21600.0))
(setq *OY* '(-560996.0 -555996.0 -553596.0 -548596.0) *NV* '(0.0 5400.0 7500.0 12900.0))
(defun logm (s / f) (setq f (open (strcat *S* "p2_log.txt") "a")) (write-line s f) (close f))
(defun mklay (n lw) (if (not (tblsearch "LAYER" n)) (command "_.-LAYER" "_N" n "_LW" lw n "")))
(defun rc (lay a b)
  (entmake (list '(0 . "LWPOLYLINE") '(100 . "AcDbEntity") (cons 8 lay) '(100 . "AcDbPolyline") '(90 . 4) '(70 . 1)
    (cons 10 (list (car a) (cadr a))) (cons 10 (list (car b) (cadr a)))
    (cons 10 (list (car b) (cadr b))) (cons 10 (list (car a) (cadr b))))))
(defun bb (e / o a b r)
  (setq o (vlax-ename->vla-object e))
  (setq r (vl-catch-all-apply 'vla-getboundingbox (list o 'a 'b)))
  (if (vl-catch-all-error-p r) nil (list (vlax-safearray->list a) (vlax-safearray->list b))))
(defun tx (lay p h s rot j)
  (entmake (list '(0 . "TEXT") (cons 8 lay) (cons 7 "Isocpeur") (cons 10 p) (cons 11 p) (cons 40 h) (cons 1 s)
    (cons 50 rot) (cons 72 (if (= j "ML") 0 1)) (cons 73 2))))
(defun settext (e s / d) (setq d (entget e)) (entmod (subst (cons 1 s) (assoc 1 d) d)))
(defun cpy (e dx dy) (command "_.COPY" e "" "0,0" (strcat (rtos dx 2 2) "," (rtos dy 2 2)) "") (entlast))
(defun mv (e dx dy) (command "_.MOVE" e "" "0,0" (strcat (rtos dx 2 4) "," (rtos dy 2 4))))
(defun sheetk (dx num name ttl)
  (cpy (handent "1E6700") dx 0.0)
  (cpy (handent "1E6701") dx 0.0)
  (settext (cpy (handent "1E6702") dx 0.0) name)
  (settext (cpy (handent "1E6704") dx 0.0) num)
  (if ttl (settext (cpy (handent "1E6706") dx 0.0) ttl))
  (logm (strcat "sheet " num)))
(defun plancp (lst dx / ss e mk d n p)
  (setq ss (ssadd))
  (foreach h lst (if (setq e (handent h)) (ssadd e ss)))
  (logm (strcat "plan n=" (itoa (sslength ss))))
  (setq mk (entlast))
  (command "_.COPY" ss "" "0,0" (strcat (rtos dx 2 2) ",0") "")
  (setq e (entnext mk) n 0)
  (while e
    (setq d (entget e))
    (if (and (= (cdr (assoc 0 d)) "LWPOLYLINE") (assoc 6 d))
      (progn (entmod (subst '(6 . "ByLayer") (assoc 6 d) d)) (setq n (1+ n))))
    (if (= (cdr (assoc 0 d)) "DIMENSION")
      (progn
        (setq p (cdr (assoc 10 d)))
        (cond ((< (cadr p) (+ *Y0* 10500.0 -1000.0)) (mv e 0.0 -900.0))
              ((< (car p) (+ *X35* 9500.0 -1000.0)) (mv e -500.0 0.0)))))
    (setq e (entnext e)))
  (logm (strcat "plan lt reset " (itoa n))))
(defun dl (a b c / ol) (setq ol (getvar "CLAYER")) (setvar "CLAYER" "Размеры") (command "_.DIMLINEAR" a b c) (setvar "CLAYER" ol))
(defun pw (x xs us / i)
  (cond ((<= x (car xs)) (+ (car us) (- x (car xs))))
        ((>= x (last xs)) (+ (last us) (- x (last xs))))
        (t (setq i 0)
           (while (> x (nth (1+ i) xs)) (setq i (1+ i)))
           (+ (nth i us) (* (- x (nth i xs)) (/ (- (nth (1+ i) us) (nth i us)) (- (nth (1+ i) xs) (nth i xs))))))))
(defun near (x lst tol / r) (setq r nil) (foreach a lst (if (< (abs (- x a)) tol) (setq r a))) r)
(defun keepsec (u v w h / a)
  (if (> w h)
    (cond ((near u '(0.0 21600.0) 700) (and (> v -400) (< v 13300)))
          ((near u '(8950.0 12650.0) 700) (or (and (> v 7100) (< v 13300)) (and (> v -400) (< v 5800))))
          (t nil))
    (and (near v '(0.0 5400.0 7500.0 12900.0) 700) (> u -400) (< u 22000))))
(defun analog (/ mk lst e d b typ cx cy u v w h ns nk ne n5 n4 nn dy)
  (setq dy (- *Y0* -574724.0))
  (setq mk (entlast))
  (command "_.-INSERT" (strcat "*" *S* "analog45.dwg") "0,0" "1" "0")
  (setq e (entnext mk) lst nil)
  (while e (setq lst (cons e lst) e (entnext e)))
  (logm (strcat "analog ents " (itoa (length lst))))
  (setq ns 0 nk 0 ne 0 n5 0 n4 0 nn 0)
  (foreach e lst
    (setq d (entget e) typ (cdr (assoc 0 d)) b (bb e))
    (cond
      ((null b) (setq nn (1+ nn)) (logm (strcat "nobb " typ " " (cdr (assoc 5 d)))))
      ((= typ "SPDSSECTION")
        (setq cx (/ (+ (car (car b)) (car (cadr b))) 2.0) cy (/ (+ (cadr (car b)) (cadr (cadr b))) 2.0)
              w (- (car (cadr b)) (car (car b))) h (- (cadr (cadr b)) (cadr (car b)))
              u (pw cx *OX* *NU*) v (pw cy *OY* *NV*))
        (if (and (keepsec u v w h) (not (and (< (abs (+ cx 473058.0)) 60.0) (< (abs (+ cy 551036.0)) 60.0))))
          (progn (mv e (- (+ *X35* 9500.0 u) cx) (- (+ *Y0* 10500.0 v) cy)) (setq nk (1+ nk)))
          (progn (entdel e) (setq ns (1+ ns)))))
      ((>= (/ (+ (car (car b)) (car (cadr b))) 2.0) -446323.0)
        (mv e 94500.0 dy) (setq n5 (1+ n5))
        (if (= typ "ACAD_TABLE") (setq *TBL* (cons e *TBL*))))
      ((>= (car (car b)) -459600.0) (mv e 118477.0 -417018.0) (setq n4 (1+ n4)))
      (t (entdel e) (setq ne (1+ ne)))))
  (logm (strcat "sec kept " (itoa nk) " dropped " (itoa ns) " s5 " (itoa n5) " s4sec " (itoa n4) " erased " (itoa ne) " nobb " (itoa nn))))
(defun tables (sp vd / o cols)
  (foreach t1 *TBL*
    (setq o (vlax-ename->vla-object t1) cols (vla-get-columns o))
    (foreach x (if (= cols 13) sp vd) (vla-settext o (car x) (cadr x) (caddr x)))
    (logm (strcat "table cols " (itoa cols)))))
;;BODY
(defun c:P2 (/ r)
  (setvar "CMDECHO" 0) (setvar "OSMODE" 0)
  (mklay "КЖ_Фундамент" "0.30")
  (if (tblsearch "DIMSTYLE" "СПДС") (command "_.-DIMSTYLE" "_R" "СПДС"))
  (setq r (vl-catch-all-apply 'p2_body nil))
  (if (vl-catch-all-error-p r) (logm (strcat "ERR " (vl-catch-all-error-message r))) (logm "body ok"))
  (command "_.ZOOM" "_E")
  (command "_.SAVEAS" "2018" "%OUT%")
  (logm "saved")
  (princ))
