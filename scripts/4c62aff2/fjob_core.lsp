(vl-load-com)
(setq *S* "C:/Users/Admin/AppData/Local/Temp/claude/210ab68cad67e8c1/4c62aff2-a55a-4637-9af2-523dd75c9ccb/scratchpad/")
(defun logm (s / f) (setq f (open (strcat *S* "fjob_log.txt") "a")) (write-line s f) (close f))
(defun mklay (n lw lt)
  (if (not (tblsearch "LAYER" n)) (command "_.-LAYER" "_N" n "_LW" lw n ""))
  (if lt (command "_.-LAYER" "_LT" lt n "")))
(defun rc (lay a b)
  (entmake (list '(0 . "LWPOLYLINE") '(100 . "AcDbEntity") (cons 8 lay) '(100 . "AcDbPolyline") '(90 . 4) '(70 . 1)
    (cons 10 (list (car a) (cadr a))) (cons 10 (list (car b) (cadr a)))
    (cons 10 (list (car b) (cadr b))) (cons 10 (list (car a) (cadr b))))))
(defun ln (lay a b) (entmake (list '(0 . "LINE") (cons 8 lay) (cons 10 a) (cons 11 b))))
(defun tx (lay p h s rot j)
  (entmake (list '(0 . "TEXT") (cons 8 lay) (cons 7 "Isocpeur") (cons 10 p) (cons 11 p) (cons 40 h) (cons 1 s)
    (cons 50 rot) (cons 72 (if (= j "ML") 0 1)) (cons 73 2))))
(defun hl (/ e ol)
  (setq e (entlast) ol (getvar "CLAYER"))
  (setvar "CLAYER" "КЖ_Штрих")
  (command "_.-HATCH" "_P" "ANSI36" "20" "0" "_S" e "" "")
  (setvar "CLAYER" ol))
(defun settext (e s / d) (setq d (entget e)) (entmod (subst (cons 1 s) (assoc 1 d) d)))
(defun cpy (e dx dy) (command "_.COPY" e "" "0,0" (strcat (rtos dx 2 2) "," (rtos dy 2 2)) "") (entlast))
(defun sheet (k num name ttl / dx)
  (setq dx (* 42000.0 k))
  (cpy (handent "1B3986") dx 0.0)
  (cpy (handent "1B3A03") dx 0.0)
  (settext (cpy (handent "1B3A04") dx 0.0) name)
  (settext (cpy (handent "1B3A06") dx 0.0) num)
  (if (/= k 9) (settext (cpy (handent "1B3A08") dx 0.0) ttl))
  (logm (strcat "sheet " num)))
(defun hss (lst / ss e) (setq ss (ssadd)) (foreach h lst (if (setq e (handent h)) (ssadd e ss))) ss)
(defun plancopy (k filt / ss dx mk e d n)
  (setq dx (+ 3223.0 (* 42000.0 k)))
  (setq ss (hss (if filt *PLANF* *PLAN*)))
  (logm (strcat "plancopy " (itoa k) " n=" (itoa (sslength ss))))
  (setq mk (entlast))
  (command "_.COPY" ss "" "0,0" (strcat (rtos dx 2 2) ",-493878") "")
  (if (not filt)
    (progn (setq e (entnext mk) n 0)
      (while e
        (setq d (entget e))
        (if (and (= (cdr (assoc 0 d)) "LWPOLYLINE") (= (cdr (assoc 8 d)) "Размеры"))
          (progn (command "_.CHPROP" e "" "_LT" "HIDDEN" "_S" "20" "") (setq n (1+ n))))
        (setq e (entnext e)))
      (logm (strcat "hidden n=" (itoa n))))))
(defun seccopy (k / ss)
  (setq ss (hss *SEC*))
  (logm (strcat "seccopy n=" (itoa (sslength ss))))
  (command "_.COPY" ss "" "0,0" "346077,-418218" "")
  (logm "seccopy done"))
;;BODY
(defun c:FJOB (/ r)
  (setvar "CMDECHO" 0) (setvar "OSMODE" 0) (setvar "OSNAPCOORD" 1)
  (if (not (tblsearch "LTYPE" "HIDDEN")) (command "_.-LINETYPE" "_L" "HIDDEN" "acadiso.lin" ""))
  (mklay "КЖ_ФБС" "0.30" nil) (mklay "КЖ_Монолит" "0.30" nil) (mklay "КЖ_Штрих" "0.05" nil)
  (mklay "КЖ_Марки" "0.05" nil) (mklay "КЖ_Плиты" "0.30" nil) (mklay "КЖ_Плиты_т" "0.05" nil)
  (mklay "КЖ_Таблица" "0.05" nil) (mklay "КЖ_Таблица_т" "0.30" nil)
  (setq r (vl-catch-all-apply 'fjob_body nil))
  (if (vl-catch-all-error-p r) (logm (strcat "ERR " (vl-catch-all-error-message r))) (logm "body ok"))
  (command "_.ZOOM" "_E")
  (command "_.SAVEAS" "2018" "%OUT%")
  (logm "saved")
  (princ))
