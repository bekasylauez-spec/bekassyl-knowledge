(vl-load-com)
(defun c:PROBE (/ ss i e o f)
  (setq f (open "C:/Users/Admin/AppData/Local/Temp/claude/210ab68cad67e8c1/4c62aff2-a55a-4637-9af2-523dd75c9ccb/scratchpad/probe.txt" "w"))
  (setq ss (ssget "_X" '((0 . "SPDSLEVELMARK"))))
  (write-line (strcat "n=" (if ss (itoa (sslength ss)) "0")) f)
  (if ss (progn
    (setq e (ssname ss 0) o (vlax-ename->vla-object e))
    (write-line (strcat "handle " (cdr (assoc 5 (entget e)))) f)
    (foreach p '("Text" "Value" "Level" "Mark" "Elevation" "TextValue" "LevelValue" "Text1" "Height" "Name")
      (write-line (strcat p " = " (vl-princ-to-string (vl-catch-all-apply 'vlax-get-property (list o p)))) f))
    (close f)
    (setq f nil)
    (setvar "LOGFILEMODE" 1)
    (vlax-dump-object o T)))
  (if f (close f))
  (princ))
