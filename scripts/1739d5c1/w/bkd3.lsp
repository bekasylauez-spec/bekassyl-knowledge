(defun bk:s (v) (if v (vl-princ-to-string v) "-"))
(defun bk:in (p)
  (and (listp p) (numberp (car p))
       (> (car p) (atof (getenv "BX0"))) (< (car p) (atof (getenv "BX1")))
       (> (cadr p) (atof (getenv "BY0"))) (< (cadr p) (atof (getenv "BY1")))))
(defun bk:row (e ed typ / o)
  (strcat typ "\t" (cdr (assoc 8 ed)) "\tlt=" (bk:s (cdr (assoc 6 ed))) "\tlw=" (bk:s (cdr (assoc 370 ed))) "\tc=" (bk:s (cdr (assoc 62 ed)))
    (cond
      ((= typ "DIMENSION")
       
       (strcat "\tst=" (cdr (assoc 3 ed)) "\tm=" (rtos (cdr (assoc 42 ed)) 2 1) "\tt=" (bk:s (cdr (assoc 1 ed)))
               "\tp10=" (bk:s (cdr (assoc 10 ed))) "\tp11=" (bk:s (cdr (assoc 11 ed))) "\tp13=" (bk:s (cdr (assoc 13 ed))) "\tp14=" (bk:s (cdr (assoc 14 ed)))
               "\txd=" (bk:s (assoc -3 (entget e '("ACAD"))))))
      ((member typ '("TEXT" "MTEXT"))
       (strcat "\t" (bk:s (cdr (assoc 1 ed))) "\th=" (bk:s (cdr (assoc 40 ed))) "\tst=" (bk:s (cdr (assoc 7 ed))) "\tp=" (bk:s (cdr (assoc 10 ed)))))
      ((= typ "LWPOLYLINE")
       (strcat "\tn=" (itoa (cdr (assoc 90 ed))) "\tw=" (bk:s (cdr (assoc 43 ed))) "\tcl=" (bk:s (cdr (assoc 70 ed)))
               "\tv=" (apply 'strcat (mapcar '(lambda (q) (if (= (car q) 10) (strcat " " (rtos (cadr q) 2 1) "," (rtos (caddr q) 2 1)) "")) ed))))
      ((= typ "LINE")
       (strcat "\tp=" (bk:s (cdr (assoc 10 ed))) " " (bk:s (cdr (assoc 11 ed))) "\tlts=" (bk:s (cdr (assoc 48 ed)))))
      ((= typ "INSERT")
       (strcat "\tb=" (cdr (assoc 2 ed)) "\tp=" (bk:s (cdr (assoc 10 ed))) "\ts=" (bk:s (cdr (assoc 41 ed)))))
      (T ""))))
(defun c:BKD3 (/ f ss i e ed typ r)
  (setq f (open (getenv "BKOUT") "w"))
  (setq ss (ssget "_X" '((410 . "Model"))) i 0)
  (repeat (sslength ss)
    (setq e (ssname ss i) ed (entget e) i (1+ i) typ (cdr (assoc 0 ed)))
    (setq r (vl-catch-all-apply '(lambda () (if (bk:in (cdr (assoc 10 ed))) (write-line (bk:row e ed typ) f)))))
    (if (vl-catch-all-error-p r) (write-line (strcat "ERR " typ " " (vl-catch-all-error-message r)) f)))
  (close f)
  (princ))
